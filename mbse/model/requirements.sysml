package XDesignRequirements {
    @XDesignCommon::DiagramPresentation { label = "Requirements"; }
    @XDesignCommon::DocSection { document = "docs/requirements/requirements.md"; section = "R01"; }
    private import ScalarValues::*;
    private import Requirements::*;

    doc /* The requirements baseline for this tool, written outwards from requirements.
       A requirement states what the tool must do and records why it must; a wish that
       asked for it is named in that wish's own record, never here. Nothing in this
       package references a wish. */

    requirement def XDesignRequirement :> DesignConstraintCheck {
        @XDesignCommon::DocSection { document = "docs/requirements/requirements.md"; section = "R01"; }
        doc /* A requirement on this tool, carrying the reason it exists, so a reader can
           judge the requirement instead of taking it on authority. */
        attribute rationale : String;
    }

    requirement checkpointSourceIsProjectOwned : XDesignRequirement {
        @XDesignCommon::DocSection { document = "docs/requirements/requirements.md"; section = "R16"; }
        doc /* A reusable checkpoint definition and its scripts belong to the
           selected project's engineering source. A run retains its resolved
           rules, criteria and executor selection separately from mutable source. */
        attribute redefines rationale = "Installing or updating xdesign must not move a user's project checks into the tool repository or rewrite a previously registered definition.";
    }

    requirement configuredChecksRetainAuthority : XDesignRequirement {
        @XDesignCommon::DocSection { document = "docs/requirements/requirements.md"; section = "R16"; }
        doc /* Configured syntactic evaluations retain script authority, the
           checker identity, assessed revision and evidence. A working agent's
           supplied semantic judgment is a separate result, not a check executor. */
        attribute redefines rationale = "Readers need the actual checker and reviewed snapshot to interpret a result without confusing a supplied semantic judgment with a script assessment.";
    }

    requirement operatorDelegatesRunState : XDesignRequirement {
        @XDesignCommon::DocSection { document = "docs/requirements/requirements.md"; section = "R16"; }
        doc /* The embedded local operator projects stored run facts and delegates
           lifecycle changes to init/next/check. Checkpoint authoring changes source;
           it does not create a passed assessment or start stage work. */
        attribute redefines rationale = "A second mutable UI status or an implicit stage-work launch would make the displayed history disagree with the flow's recorded decisions.";
    }

    requirement sharedChecksHavePinnedOrigins : XDesignRequirement {
        @XDesignCommon::DocSection { document = "docs/requirements/requirements.md"; section = "R16"; }
        doc /* Proposed cross-project obligation, not implemented: an imported
           definition identifies its namespace and upstream revision and pins the
           exact definition, executor bundle and project input mapping. A later
           upstream update cannot change an existing binding. */
        attribute redefines rationale = "The same local slug or script path can name unrelated bytes in two projects; sharing requires immutable content identity and explicit adaptation.";
    }

    requirement crossProjectHistoryKeepsItsOwner : XDesignRequirement {
        @XDesignCommon::DocSection { document = "docs/requirements/requirements.md"; section = "R16"; }
        doc /* Proposed federation obligation, not implemented: a history reference
           identifies project, store, item, immutable revision and assessment.
           Aggregation remains a projection of each project's authority and shows
           unavailable sources explicitly. Preservation also requires a verified
           backup/restore contract before the store is a sole archive. */
        attribute redefines rationale = "A project path or wish ID is not globally unique, and a central status cache cannot preserve the evidence or authority of its source projects.";
    }

    requirement checkpointKindIsDeclared : XDesignRequirement {
        @XDesignCommon::DocSection { document = "docs/requirements/requirements.md"; section = "R01"; }
        doc /* Every checkpoint declares whether its criteria are established
           syntactically, by a fixed code or script check, or semantically, by
           judgment. */
        attribute redefines rationale = "A flow can route a check to the right executor, a script or a judging reader, only if the checkpoint says which kind it is.";
    }

    requirement syntacticCheckIsFixed : XDesignRequirement {
        @XDesignCommon::DocSection { document = "docs/requirements/requirements.md"; section = "R01"; }
        doc /* A syntactic checkpoint names at least one checker whose command fixes the
           check, so the flow runs it unchanged rather than judging afresh. */
        attribute redefines rationale = "Repeating the same criteria by hand invites drift; a fixed command makes one check reproducible and its output comparable across revisions.";
    }

    requirement syntacticAssessmentIsScripted : XDesignRequirement {
        @XDesignCommon::DocSection { document = "docs/requirements/requirements.md"; section = "R01"; }
        doc /* An assessment of a syntactic checkpoint is judged by a script, and the
           script's output for the assessed revision is its evidence. */
        attribute redefines rationale = "A script cannot rationalize a result, and its output can be re-examined later, which is what makes the evidence worth keeping.";
    }

    requirement semanticCheckNamesItsJudges : XDesignRequirement {
        @XDesignCommon::DocSection { document = "docs/requirements/requirements.md"; section = "R01"; }
        doc /* A semantic checkpoint names no checker and states whether an agent or a
           human may judge it. */
        attribute redefines rationale = "Criteria such as whether parts address requirements cannot be reduced to a command, so the checkpoint must say who is competent to judge them.";
    }

    requirement checkerStatesItsConformance : XDesignRequirement {
        @XDesignCommon::DocSection { document = "docs/requirements/requirements.md"; section = "R01"; }
        doc /* A checker states which kinds of conformance it establishes over the
           stage's artifacts: artifact presence, identifier conformance, definition
           coverage or trace conformance. */
        attribute redefines rationale = "A reader who knows what a check covers also knows what it leaves uncovered, and that uncovered part is where judgment is still needed.";
    }

    requirement wishProductsAreRetained : XDesignRequirement {
        @XDesignCommon::DocSection { document = "docs/requirements/requirements.md"; section = "R01"; }
        doc /* The requirements a wish produces, and the model modifications it causes,
           are retained in this model. A wish's own record may describe them, but it
           never holds the only copy. */
        attribute redefines rationale = "A wish record is a working record: it is rewritten as a wish advances and may move out of SysML entirely. Design kept only there would be lost to the project, so the model keeps the substance while the wish record keeps the account of how it came about.";
    }

    requirement modelStandsWithoutWishes : XDesignRequirement {
        @XDesignCommon::DocSection { document = "docs/requirements/requirements.md"; section = "R01"; }
        doc /* The project model resolves and checks on its own. No model element names a
           wish or a wish record, and no model element carries a wish's identity; a wish
           may reference model elements, never the reverse. */
        attribute redefines rationale = "A model that needed wish records in order to check would make those records load-bearing, and then rewriting one as a wish advances, or moving wish records out of SysML, would break the model.";
    }

    requirement flowRunIsRealizedByDesign : XDesignRequirement {
        @XDesignCommon::DiagramPresentation { label = "Run has a concrete design"; summary = "Run class, factory and operations"; }
        @XDesignCommon::DocSection { document = "docs/requirements/requirements.md"; section = "R01"; }
        doc /* A flow's run is realized by design elements: a class for the run, a
           factory that creates it, and the functions that evaluate its gates and
           advance it. */
        attribute redefines rationale = "The architecture says what a flow is made of; only a design says what it is made into. Without one, every implementation of a flow re-invents its run, its visits and the way its gates are judged.";
    }

    requirement designedFlowGatesEveryStage : XDesignRequirement {
        @XDesignCommon::DiagramPresentation { label = "Every stage has an exit gate"; summary = "Advancement requires explicit authorization"; }
        @XDesignCommon::DocSection { document = "docs/requirements/requirements.md"; section = "R01"; }
        doc /* Every stage of a designed flow declares the exit checkpoint that must
           pass before the flow leaves it. */
        attribute redefines rationale = "A stage left without a gate completes on the mere passage of work; gating every stage makes a designed flow's advancement checkable everywhere, not only at its end.";
    }

    requirement gateSyntaxIsRunnable : XDesignRequirement {
        @XDesignCommon::DocSection { document = "docs/requirements/requirements.md"; section = "R01"; }
        doc /* Every syntactic gate's checker names a command that exists in the
           repository; the flow runs it unchanged, and its output for the assessed
           revision is the evidence. */
        attribute redefines rationale = "A gate whose command does not exist can never pass by its own rule, and the work would either stall at the gate or fall back to unrecorded judgment.";
    }

    requirement runRecordIsScriptChecked : XDesignRequirement {
        @XDesignCommon::DocSection { document = "docs/requirements/requirements.md"; section = "R01"; }
        doc /* The conformance of a run's record — at least one visit per stage,
           assessments cited at the visited revision, evidence that exists — is
           established by a checker, not by reading. */
        attribute redefines rationale = "These invariants were kept by reading; reading does not re-run per revision and does not fail a record rather than trusting a reader to notice.";
    }

    requirement designCarriesItsDocSections : XDesignRequirement {
        @XDesignCommon::DocSection { document = "docs/requirements/requirements.md"; section = "R01"; }
        doc /* Every element of the detailed design carries the documentation section
           that covers it, and the design's own checker establishes that the sections
           are present and well formed. */
        attribute redefines rationale = "A design read from declarations alone forces the reader to reconstruct the reasoning; the section carries it, and a checker keeps the map from rotting as the design changes.";
    }

    requirement checkerRulesAreDeclared : XDesignRequirement {
        @XDesignCommon::DocSection { document = "docs/requirements/requirements.md"; section = "R01"; }
        doc /* Every checker of a designed flow declares the rules by which its
           outcome is determined — each rule's exact condition and what it reads —
           and its command reports each rule's verdict; the design's check
           establishes that the declared rules and the command's rule list agree. */
        attribute redefines rationale = "A checker that only names a command hides its logic in code, and the model cannot say why a gate passed or what would make it fail. Declared rules make the outcome follow from stated conditions, and the agreement check keeps the model's copy and the command's copy from drifting apart.";
    }

    requirement structureGraphsAreDocumented : XDesignRequirement {
        @XDesignCommon::DiagramPresentation { label = "Nine views document the design"; summary = "Each view selects native elements and locates its figure"; }
        @XDesignCommon::DocSection { document = "docs/requirements/requirements.md"; section = "R01"; }
        doc /* A designed flow declares nine complementary views of the same model:
           block definition, internal block, requirements, parametric, use case,
           activity, sequence, state machine and package. Each view selects native
           model elements, locates a rendered figure and its documentation section,
           and states what question it answers. A check establishes that every
           declared figure exists and is referenced. */
        attribute redefines rationale = "A timeline, a logical graph and an interface graph alone leave actor goals, requirement satisfaction and verification, authorization constraints, lifecycle guards and package dependencies unexplained. Nine coordinated views expose these concerns without maintaining a second model.";
    }

    requirement runRealizesItsDesign : XDesignRequirement {
        @XDesignCommon::DocSection { document = "docs/requirements/requirements.md"; section = "R01"; }
        doc /* A run of a designed flow is recorded with the design's class, so the
           design is realized by the run rather than declared beside it. */
        attribute redefines rationale = "A class nothing is typed by is a picture of a run, not a run's design; the typing is what makes the design load-bearing, and a check can establish it.";
    }

    requirement diagramViewsAreReadable : XDesignRequirement {
        @XDesignCommon::DocSection { document = "docs/requirements/requirements.md"; section = "R01"; }
        @XDesignCommon::DiagramPresentation { label = "Nine views are readable"; summary = "Review final figures at article size"; }
        doc /* The nine primary SimpleFlow documentation views are legible at a
           900-pixel article width, with displayed diagram text at least 11 pixels,
           no clipped labels or node overlaps, and relationships whose endpoints
           remain identifiable. Each view focuses on one question and uses its
           own diagram notation: visible internal boundaries and ports, parameter
           bindings, actor goals inside the subject boundary, and readable guards.
           Full-model membership trees remain expandable reference overviews.
           Final SVGs and their matching previews receive a visual review in
           addition to compiler and semantic checks. */
        attribute redefines rationale = "A complete inventory of model elements does not explain their relationships when labels shrink, edges obscure one another or diagram notation is flattened. A measured display size and review of the actual delivered figures make readability an explicit delivery obligation.";
    }

    requirement diagramPresentationRetainsSourceIdentity : XDesignRequirement {
        @XDesignCommon::DocSection { document = "docs/requirements/requirements.md"; section = "R01"; }
        @XDesignCommon::DiagramPresentation { label = "Figures retain model identity"; summary = "Short labels preserve native source references"; }
        doc /* Documentation diagrams derive their selected elements and
           relationships from native SysML views and compiler exports. Optional
           presentation metadata supplies short labels, summaries and the question
           a view answers while native qualified names, full descriptions and
           endpoint identities remain available through tooltips or source
           references. A final figure manifest records source and SVG hashes,
           generation parameters and the preview correspondence used in review,
           so stale previews cannot authorize changed figures. */
        attribute redefines rationale = "Readable composition needs less text on the page, but readers must still be able to identify the actual modeled element, inspect omitted detail and reproduce the figure that was accepted. Presentation metadata and final-artifact provenance prevent a second, disconnected diagram model.";
    }

    requirement documentationEntryMapsDesign : XDesignRequirement {
        @XDesignCommon::DocSection { document = "docs/requirements/requirements.md"; section = "R01"; }
        doc /* The documentation set has one entry document that gives each reader a
           route through the current documents and maps the model's modules and
           current design concerns to their detailed sections. */
        attribute redefines rationale = "Without an entry and a model-to-document map, readers must infer the document set and reconstruct the relationship between the system design and its explanations.";
    }

    requirement documentationSupportsMultipleFlows : XDesignRequirement {
        @XDesignCommon::DocSection { document = "docs/requirements/requirements.md"; section = "R01"; }
        doc /* The documentation structure has an independently addressable overview
           for each defined flow and a separate detailed location for each developed
           flow design. Another flow can be added without renumbering or recasting
           existing flow sections. */
        attribute redefines rationale = "The project can run more than one flow; a document hierarchy tied to the current SimpleFlow would hide another flow or force an unrelated design into its pages.";
    }

    requirement figuresStayWithDesignExplanation : XDesignRequirement {
        @XDesignCommon::DocSection { document = "docs/requirements/requirements.md"; section = "R01"; }
        doc /* Each documented design figure is embedded in the subsection whose
           design question it answers and accompanied there by its native view,
           companion views, status, reading guidance, and limits. */
        attribute redefines rationale = "A disconnected image catalog makes readers join the design claim, source projection, and interpretation themselves; a local explanation lets them judge what the figure establishes.";
    }

    requirement modelDocumentationLinksResolve : XDesignRequirement {
        @XDesignCommon::DocSection { document = "docs/requirements/requirements.md"; section = "R01"; }
        doc /* A documentation check resolves every DocSection document and stable
           section anchor, every DocFigure asset and carrying document, and each
           figure's embed in that document; the entry's module-level reverse index
           agrees with the annotated modules and sections it lists. */
        attribute redefines rationale = "A locator that names a missing section or unembedded figure gives false confidence that the model is explained; a repeatable audit detects drift as either side changes.";
    }

    requirement viewAndViewpointRolesAreSpecified : XDesignRequirement {
        @XDesignCommon::DocSection { document = "docs/requirements/requirements.md"; section = "R01"; }
        doc /* The documentation specification distinguishes a viewpoint's question
           and selection convention from a native SysML view's selected elements,
           and identifies how the view, DocFigure, rendered asset, and carrying
           DocSection answer that question together. It states applicability of
           the nine reference diagram concerns for each designed flow. */
        attribute redefines rationale = "An image alone cannot tell a reader which concern selected its elements or whether omitted diagrams were inapplicable; explicit roles keep the figure tied to the model and expose coverage decisions.";
    }

    requirement checkerRulesAreImplementationReady : XDesignRequirement {
        @XDesignCommon::DocSection { document = "docs/requirements/requirements.md"; section = "R01"; }
        doc /* Each documented design-stage checker rule states its input artifacts,
           exact decision condition, failure diagnostic, evidence output, and
           current implementation status so a later implementation can reproduce
           the specified result. */
        attribute redefines rationale = "Rule names and broad criteria leave later implementers to invent the actual check; operational inputs, conditions and outputs make the intended gate reproducible while status prevents a planned check being mistaken for a running one.";
    }

    requirement rustUmlDesignMapsEveryDesignElement : XDesignRequirement {
        @XDesignCommon::DocSection { document = "docs/requirements/requirements.md"; section = "R01"; }
        doc /* A Rust software design of a designed flow names one Rust element for
           each of the flow's design elements — the run, the factory, the checkpoint
           class and its adaptations, the gate and advance functions, the records,
           the statuses and the automation ports — and records which SysML design
           element each Rust element realizes. */
        attribute redefines rationale = "An implementation that starts from an unmapped design re-decides the structure the design already fixed, and a reviewer cannot tell whether the crate covers the design or quietly drops part of it; the mapping makes coverage inspectable before any code exists.";
    }

    requirement umlViewsAreSelectedWithReasons : XDesignRequirement {
        @XDesignCommon::DocSection { document = "docs/requirements/requirements.md"; section = "R01"; }
        doc /* For a module's UML design, every UML view of the project's UML guide
           is marked required, recommended or not applicable with a reason, and each
           adopted view is embedded in the section whose question it answers, with
           its figure block and an honest render status. */
        attribute redefines rationale = "A design that shows only the views someone happened to draw hides whether the others were considered; stated applicability lets a reviewer distinguish a reasoned omission from an overlooked one, and the figure block keeps each adopted view tied to its question and source.";
    }

    requirement softwareDesignClaimsNoImplementation : XDesignRequirement {
        @XDesignCommon::DocSection { document = "docs/requirements/requirements.md"; section = "R01"; }
        doc /* A software design document distinguishes designed elements from
           implemented code and claims no implementation, test result or build that
           does not exist in the repository. */
        attribute redefines rationale = "A design read as a finished product sends integrators looking for code that is not there and hides the work that remains; an explicit status keeps the design usable without pretending to be its realization.";
    }

    requirement stageCliUsesUniformInteraction : XDesignRequirement {
        @XDesignCommon::DocSection { document = "docs/requirements/requirements.md"; section = "R01"; }
        doc /* Every supported stage exposes the same next/check interaction.
           next returns current work without writes. check records collected outputs,
           assesses every exit gate, advances only when authorized, and returns the
           assessed visit plus correction work, successor work, or completion. */
        attribute redefines rationale = "Agents should follow stage content rather than coordinate separate recording, assessment and progression commands.";
    }
    requirement stageCliPreservesRunIntegrity : XDesignRequirement {
        @XDesignCommon::DocSection { document = "docs/requirements/requirements.md"; section = "R01"; }
        doc /* Independent command processes restore the same registered run and
           frozen work definitions. Reject corrupt records, changed plans, stale
           submissions and concurrent writes. Semantic judgments bind to the exact
           collected artifact snapshot and never substitute for fixed checker reports.
           Completed next/check calls are read-only; registration is explicit. */
        attribute redefines rationale = "A short command interface is useful only if process restarts and corrections preserve evidence, authority and stage identity.";
    }

    requirement operationalRecordsHaveDurableAuthority : XDesignRequirement {
        @XDesignCommon::DocSection { document = "docs/requirements/requirements.md"; section = "R01"; }
        doc /* New wish registrations, flow run facts, revision manifests, material
           and evidence bytes, and operation receipts persist in a local operational
           store outside regenerable cache. Git retains engineering definitions and
           products; existing Git wish traces remain legacy records. */
        attribute redefines rationale = "A run whose only authoritative record lives under cache can lose the account of what executed and which bytes were judged; separating operational facts from engineering products gives each an explicit durable authority.";
    }

    requirement wishHistoryIsRevisioned : XDesignRequirement {
        @XDesignCommon::DocSection { document = "docs/requirements/requirements.md"; section = "R01"; }
        doc /* A generic store item has a stable identity and kind. Each wish save
           appends an immutable, numbered revision containing typed metadata and a
           complete URI-to-material manifest. List, get, history, read and checkout
           expose the selected revision without deleting earlier revisions. */
        attribute redefines rationale = "A mutable current JSON snapshot cannot explain earlier decisions or reproduce an earlier checked state; complete retained revisions make wish history inspectable and recoverable without hard-coding the store to one future item kind.";
    }

    requirement materialsAreContentAddressed : XDesignRequirement {
        @XDesignCommon::DocSection { document = "docs/requirements/requirements.md"; section = "R01"; }
        doc /* Every stored material is identified by the SHA-256 of its exact bytes
           and bound to a logical URI in each revision manifest. Publication is atomic,
           identical bytes deduplicate, and read and checkout verify byte length and
           digest through end of file before returning content. */
        attribute redefines rationale = "A path alone does not identify the evidence that was judged; content identity prevents later edits from silently replacing historical bytes and makes loss or corruption detectable.";
    }

    requirement storageSaveIsAtomicAndIdempotent : XDesignRequirement {
        @XDesignCommon::DocSection { document = "docs/requirements/requirements.md"; section = "R01"; }
        doc /* A save names an operation ID, exact request bytes and expected head.
           The store durably reserves the operation before blob publication, commits
           the complete revision and receipt in one SQLite transaction, and exposes
           outcome reconciliation. Repeating the same operation and request has no
           second effect; a changed request or stale head cannot overwrite another
           writer. One stage check is saved as one logical operation. */
        attribute redefines rationale = "Process crashes and retries must not duplicate work or leave run rows without their evidence; explicit guards and receipts turn uncertain outcomes into inspectable recovery instead of silent overwrite.";
    }

    requirement workingCacheIsRecoverable : XDesignRequirement {
        @XDesignCommon::DocSection { document = "docs/requirements/requirements.md"; section = "R01"; }
        doc /* Runtime plans, work definitions, wish working sources, run records and
           checker exchanges can be regenerated from the store after their cache copies
           are deleted. Checkout restores every byte in a selected revision manifest,
           and the restored SimpleFlow record remains acceptable to its record checker. */
        attribute redefines rationale = "Treating cache as disposable is safe only when every required operational byte has a durable copy and the restored record remains usable by the existing flow contract.";
    }

    requirement wishStatusProjectsFlowExecution : XDesignRequirement {
        @XDesignCommon::DocSection { document = "docs/requirements/requirements.md"; section = "R01"; }
        doc /* Wish status and current stage shown by store queries are derived from
           the selected flow identity and stored run record. No independently editable
           wish-status flag may contradict the execution position. Generic queries can
           filter by item kind and projected wish status without hard-coding one flow. */
        attribute redefines rationale = "The flow already owns stage and completion facts; duplicating them as a separate status creates two authorities that can drift, while a projection works for future flow definitions.";
    }

    requirement storageInputAndIntegrityAreChecked : XDesignRequirement {
        @XDesignCommon::DocSection { document = "docs/requirements/requirements.md"; section = "R01"; }
        doc /* The store refuses unknown formats and schema versions, malformed or
           duplicate JSON fields, excessive inputs, unsafe logical paths and symlink
           escapes, digest mismatches, and replaced store roots or databases. Doctor
           reports missing, altered, orphan and pending storage state without converting
           integrity defects into successful reads or writes. */
        attribute redefines rationale = "Durability is not trust in whatever bytes happen to occupy a database or path; explicit refusal and diagnosis keep incompatible, unsafe or corrupted state out of engineering decisions.";
    }

    requirement releasedCheckersAreSelfContained : XDesignRequirement {
        @XDesignCommon::DocSection { document = "docs/requirements/requirements.md"; section = "R18"; }
        doc /* A released executable provides its built-in checker scripts, shared
           helper and selected SysML parser without requiring a source checkout or
           tools directory in the consumer project. Project commands are explicit. */
        attribute redefines rationale = "A repository-relative developer path cannot locate a product resource after installation, and a same-named customer file must not silently replace a built-in.";
    }
    requirement checkerExecutorsAreRetained : XDesignRequirement {
        @XDesignCommon::DocSection { document = "docs/requirements/requirements.md"; section = "R18"; }
        doc /* New store-backed runs freeze the script entry and declared helpers
           and data by digest into the plan and retain their bytes from registration.
           Edits, deletion, upgrade and cache loss do not replace that run's bundle. */
        attribute redefines rationale = "Freezing a path alone lets a later edit change what an earlier binding executes; a retained bundle identifies and recovers the actual executable inputs.";
    }
    requirement checkerExecutionUsesProjectContext : XDesignRequirement {
        @XDesignCommon::DocSection { document = "docs/requirements/requirements.md"; section = "R18"; }
        doc /* Execute a retained script with the selected project as its working
           root, optional project-local Python, private attempt temporary/cache
           paths, and recorded interpreter identity. Each project owns its sources,
           store and attempts; no implicit cross-project workspace lookup exists. */
        attribute redefines rationale = "The script installation directory is not the consumer project; inherited Python imports and shared writable output paths can mix project dependencies and evidence.";
    }

    requirement documentContractIsPortable : XDesignRequirement {
        @XDesignCommon::DocSection { document = "docs/requirements/requirements.md"; section = "R19"; }
        doc /* The documentation contract is a versioned, project-selectable
           package of rules, templates, and class paths. It can be applied to a
           different project root without relying on xdesign's Rust runtime. */
        attribute redefines rationale = "Other projects need to keep the same design-first rules while choosing their own document roots and versioning the exact contract they use.";
    }

    requirement documentAuthoringFollowsContract : XDesignRequirement {
        @XDesignCommon::DocSection { document = "docs/requirements/requirements.md"; section = "R19"; }
        doc /* A document writer resolves the permitted path from the selected
           class and slug, uses its template, requires the agreed ordered section
           headings and substantive caller-supplied content, and refuses unsafe
           paths or an unrequested overwrite. */
        attribute redefines rationale = "A generic file writer cannot enforce where a design claim belongs or whether the required chapters and content were supplied.";
    }

    requirement documentChecksReportContractGaps : XDesignRequirement {
        @XDesignCommon::DocSection { document = "docs/requirements/requirements.md"; section = "R19"; }
        doc /* Deterministic checks identify naming, section, content, locator,
           figure-block, and source-asset defects with actionable diagnostics.
           Semantic truth and final figure readability remain explicit reviews. */
        attribute redefines rationale = "A syntactically valid Markdown file or successful write does not show that a model-linked design document meets its agreed contract.";
    }

    requirement documentToolsShareOneContract : XDesignRequirement {
        @XDesignCommon::DocSection { document = "docs/requirements/requirements.md"; section = "R19"; }
        doc /* CLI and MCP operations use the same project profile, templates,
           authoring rules, and validator. A portable skill directs agents to
           use those operations in the design-first sequence. */
        attribute redefines rationale = "Different agents should receive equivalent paths and findings instead of accumulating model-specific prompt copies or protocol-specific rule forks.";
    }

    requirement documentTemplatesCoverScenarios : XDesignRequirement {
        @XDesignCommon::DocSection { document = "docs/requirements/requirements.md"; section = "R19"; }
        doc /* Proposed; no design satisfier yet. The bundled initial catalog retains
           exactly one generic default per class and multiple scenario-specific
           Markdown templates in every class. Each schema 1.1 generic or scenario
           entry packages selection and omission guidance, required inputs, a guide,
           a complete fictional example, view concerns, dependencies, deterministic
           checks, and source references. Every stored example has exactly one 64-zero
           sentinel only in its exact first-line managed marker's contract field,
           actual non-contract identity and digest version 2, no actual catalog digest,
           and no sentinel elsewhere in its bytes or another pack resource. Missing,
           duplicate, misplaced, or malformed sentinels fail before writes. All 16
           examples pass isolated consumer checks through exact one-field full-byte
           comparison and independent actual created marker/registry assertions. The
           single mixed-template example uses all five bundled classes, at least two
           template IDs in one class, and a concern-to-template or omission list,
           reuses those stored examples, and passes one whole-project check. Reviewed
           derived catalogs have their own inventory and identity and the same rule. */
        attribute redefines rationale = "A single fixed chapter list cannot guide materially different engineering questions, while unguided templates or an undefined mixed example would leave selection, depth, and coverage opaque.";
    }

    requirement documentTemplateSourcesAreInspectable : XDesignRequirement {
        @XDesignCommon::DocSection { document = "docs/requirements/requirements.md"; section = "R19"; }
        doc /* Proposed; no design satisfier yet. Every schema 1.1 catalog entry
           identifies its official or project-local sources, ideas used, retrieval and
           license facts, copying decision and any required copying review, and limits.
           A schema 1.0 compatibility projection is exempt from this entry package and
           identifies only the actual selected pack. Originality covers every catalog
           text and example; source and license adequacy receive separate review. */
        attribute redefines rationale = "Catalog content derived from research needs an inspectable basis so authors can distinguish borrowed practice, original prose, and unresolved permission or applicability questions.";
    }

    requirement documentTemplateSelectionIsExplicit : XDesignRequirement {
        @XDesignCommon::DocSection { document = "docs/requirements/requirements.md"; section = "R19"; }
        doc /* Proposed; no design satisfier yet. Within a schema 1.1 catalog,
           planning and creation accept an optional stable template identifier;
           omission or explicit selection of the generic ID selects that generic
           default. Schema 1.0 compatibility projections have no selectable template
           IDs. Creation records actual nonzero effective identity, mixed templates
           coexist in one project, and later operations never switch a document to a
           changed default. Mixed checks report each document's effective identity,
           including null template ID and digest version 1 for any schema 1.0 document.
           Reject unknown or class-mismatched IDs, caller-supplied output paths, and zero
           or multiple generic defaults for a class without writes. A 64-zero expected
           contract is invalid-request; a sentinel marker or registry identity, copied
           example, or forged sentinel registry is registry-mismatch without adoption,
           registration, or writes. */
        attribute redefines rationale = "Authors need scenario choice and inspectable per-document identity without losing existing class routes or allowing later catalog changes to redefine documents that were already authored.";
    }

    requirement documentTemplateChecksUseSelectedContract : XDesignRequirement {
        @XDesignCommon::DocSection { document = "docs/requirements/requirements.md"; section = "R19"; }
        doc /* Proposed; no design satisfier yet. Updates and deterministic checks
           first resolve the document's retained contract, including a recognized
           legacy contract, then enforce its sections, fields, and view concerns.
           Identity disagreement is judged against that effective contract, not the
           selected catalog's different release identity. An applicable concern has
           a conforming figure or a stated alternative and rationale. Diagnostics
           use the existing structured fields, and failed updates leave existing
           document bytes unchanged. No class-wide figure mandate or structural
           pass establishes semantic adequacy. */
        attribute redefines rationale = "Checks must follow the contract actually selected for each document, produce actionable evidence without destructive failure, and leave view choices and engineering meaning open to judgment.";
    }

    requirement documentTemplateCatalogPreservesCompatibility : XDesignRequirement {
        @XDesignCommon::DocSection { document = "docs/requirements/requirements.md"; section = "R19"; }
        doc /* Proposed; no design satisfier yet. Explicitly selected valid schema 1.0
           and schema 1.1 packs retain their computed digests and original behavior.
           Automatic legacy routing under a 1.1 catalog requires the exact bundled
           v1 identity; other identities fail rather than being guessed. Every 1.1
           release is immutable and later releases retain prior selectable packs.
           Unmanaged pages are not registered, reclassified, rewritten, or forced
           into a template, and managed update or figure operations refuse them.
           Valid updates preserve effective identity and registry bytes while
           changing only authorized document content. Catalog digests cover every
           authoring, checking, and compatibility resource, including exact stored
           example bytes and their one contract sentinel without digest normalization.
           A computed zero digest is invalid; valid example drift needs a new release
           and actual-digest propagation. Full-input bundled fixtures retain selected
           identity references but no actual or sentinel digest; external manifests
           contain exactly actual digest, fixture_path, and fixture_sha256, never a
           self-hash field. Separate S-12/S-16 evidence computes and retains each
           manifest's SHA-256 for stale detection. Schema 1.0 has no examples or example
           sentinel and retains digest 1fc588f652dec5e36504b9a2c9046539857094177cdfb790d88626174d2926a6.
           Drift fails closed, and resources and rendered links remain local and safe. */
        attribute redefines rationale = "Adding or upgrading a catalog must not strand existing documents or callers, confuse distinct profiles or releases, rewrite registry authority, or allow changed resources to redefine the contract under which a document was authored.";
    }

    requirement documentTemplateEvidenceIsBound : XDesignRequirement {
        @XDesignCommon::DocSection { document = "docs/requirements/requirements.md"; section = "R19"; }
        doc /* Proposed; no design satisfier yet. Template verification evidence
           identifies the assessed revision, effective contract digests and versions,
           commands and transcripts, full-input bundled fixture paths and SHA-256,
           external acceptance-manifest SHA-256 and fixture references, before and after
           hashes, diagnostics, unevaluated checks, reviewer identities and authority,
           findings, and residual risks. Correction evidence binds S-01 through S-16,
           preserves the parent run
           and evidence, retains all 26 unevaluated rules, and records later design, API,
           model, product, and test obligations without claiming them complete.
           Independent and runner judgments remain separate when both are required;
           structural output cannot substitute for either judgment. */
        attribute redefines rationale = "A catalog result is meaningful only when reviewers can inspect the exact bytes, operations, fixtures, and judgments behind it and distinguish mechanical findings from independent and runner acceptance roles.";
    }

    requirement documentTemplateCatalogSurfaceIsShared : XDesignRequirement {
        @XDesignCommon::DocSection { document = "docs/requirements/requirements.md"; section = "R19"; }
        doc /* Proposed; no design satisfier yet. CLI and MCP expose the same additive
           catalog and source data, exact template bytes, template selection and
           effective identity fields, and contract digest versions, with named catalog
           and template resources. The schema 1.0 synthesized compatibility projection
           carries null template and scenario-only fields and is not a schema 1.1
           manifest package. Selected and MCP-pinned identities use only the actual
           nonzero catalog digest; examples are not templates and neither example bytes
           nor the example sentinel become a selected contract. Existing adapter
           behavior remains separately satisfied. */
        attribute redefines rationale = "The additive catalog surface needs its own design answer rather than expanding an already satisfied adapter requirement and claiming that the current engine implements behavior it does not contain.";
    }

    requirement structuredDocumentationHasNamedRoutes : XDesignRequirement {
        @XDesignCommon::DocSection { document = "docs/requirements/requirements.md"; section = "R20"; }
        doc /* Proposed; no design satisfier yet. A selected versioned contract
           provides a per-API design route under docs/design/api/<layer>/<api>.md
           and the index, definition, implementation and views document roles under
           docs/design/flows/<flow>/. The caller selects a permitted role and semantic
           name components, not an arbitrary output path. The xdesign API route
           reserves index for a layer landing page, not an API basename. Planning
           returns the unique destination, selected identity, inputs and existence
           state without writing.
           The structured contract also retains the existing flat class routes and
           their authoring behavior; original contracts remain independently usable. */
        attribute redefines rationale = "A reusable author needs predictable destinations that reflect the ownership of an individual API or flow document, rather than putting every design page at a flat path.";
    }

    requirement apiDesignDocumentsCoverContract : XDesignRequirement {
        @XDesignCommon::DocSection { document = "docs/requirements/requirements.md"; section = "R20"; }
        doc /* Proposed; no design satisfier yet. A reusable per-API template and
           authoring guidance require caller-supplied identity, layer and kind,
           purpose, status and revision; a model realization or language-side reason;
           implementation projection; contract, behavior and constraints; and links
           to related design, requirements and planned verification as applicable.
           The contract covers signatures or type definitions, inputs, outputs,
           errors, effects and relevant invariants or a reasoned not-applicable
           decision. Project anchor policy and the xdesign unique U anchor rule apply.
           No template fabricates engineering facts or executed results. */
        attribute redefines rationale = "A dedicated API page must convey the design and its trace, not merely put a generic document at an API-shaped path.";
    }

    requirement flowDesignDocumentsCoverLayers : XDesignRequirement {
        @XDesignCommon::DocSection { document = "docs/requirements/requirements.md"; section = "R20"; }
        doc /* Proposed; no design satisfier yet. The four flow document roles have
           selectable contracts for a landing page, definition, implementation and
           views. Their required author inputs address navigation and scope; stages,
           gates and behavior; implementation allocation and source projection; and
           model views, applicability and figure references, respectively. Authored
           links and figures remain subject to the selected project rules. The kit
           does not invent a flow design, model, diagram or execution result. */
        attribute redefines rationale = "The flow directory is meaningful only when each page guides the distinct design question it owns and stays connected to the other pages.";
    }

    requirement structuredDocumentationUsesSafeOperations : XDesignRequirement {
        @XDesignCommon::DocSection { document = "docs/requirements/requirements.md"; section = "R20"; }
        doc /* Proposed; no design satisfier yet. Plan, create, check, update and
           figure attachment operate on structured destinations and their effective
           contract. Every API and flow page requires caller-supplied nonempty title,
           status, revision and a nonempty, unique list of readable project-relative
           SysML sources within configured roots. Planning may precede those sources.
           Plan reports a readable unmanaged target without adoption; creation refuses
           its collision; ordinary checking applies project checks without adoption;
           update and attachment refuse unmanaged targets. Updates and attachments
           require the current hash. Permitted figure decisions are attachable and
           prohibited decisions fail without changing the document or registry.
           Reject unsafe paths, invalid names and mismatched identities. Denied reads
           or writes produce structured diagnostics. Preserve pre-existing bytes on
           prepublication failures and report uncertain or incomplete publication:
           create's page and registry are not an atomic pair. Never modify files
           outside the selected project. */
        attribute redefines rationale = "Nested route selection must remain as safe and repeatable as the existing flat authoring operations and must not silently change an unrelated document.";
    }

    requirement structuredDocumentationKeepsVersionIdentity : XDesignRequirement {
        @XDesignCommon::DocSection { document = "docs/requirements/requirements.md"; section = "R20"; }
        doc /* Proposed; no design satisfier yet. A changed contract has a new
           version and digest. The structured contract preserves the five flat
           class routes, generic defaults and original catalog selections, including
           their required sections, fields and view decisions. The original schema
           1.0 and 1.1.0 packs remain selectable with their original bytes, digests,
           routes, markers, registry interpretations and behavior. The structured
           release resolves exact bundled-v1, bundled-1.1.0 and new identities in
           one project and supports whole-project and selected-document checks under
           each page's original effective contract. Selecting an original pack keeps
           its existing treatment of foreign identities, including a possible
           whole-project mismatch. Unrecognized or mismatched identities fail closed
           without migration, rewriting, registration or adoption. Prior wish and
           evidence records are immutable. */
        attribute redefines rationale = "A new route contract cannot silently redefine a prior release or invalidate the identity and history of a document already authored under it.";
    }

    requirement structuredDocumentationHasSharedSurfaces : XDesignRequirement {
        @XDesignCommon::DocSection { document = "docs/requirements/requirements.md"; section = "R20"; }
        doc /* Proposed; no design satisfier yet. The Python public API, JSON CLI
           and bound stdio MCP adapter expose the same structured route selections,
           template and contract information, creation and update decisions,
           validation results and effective identities. Equivalent requests have
           equivalent paths, output and diagnostics within each transport's envelope;
           MCP cannot redirect its bound project or contract. Existing supported
           calls and resources continue to work under their selected contracts. */
        attribute redefines rationale = "Authors and automation must be able to use the same structured contract independently of their chosen interface without losing existing callers.";
    }

    requirement documentKitPublicApiIsDocumented : XDesignRequirement {
        @XDesignCommon::DocSection { document = "docs/requirements/requirements.md"; section = "R20"; }
        doc /* Proposed; no design satisfier yet. Distributable kit documentation
           describes the public Python API, CLI and MCP tools and resources, including
           inputs and outputs, route selection and examples, model-source prerequisites,
           error and overwrite behavior, version and digest identity, check scope,
           incomplete or unknown publication outcomes and semantic review limits.
           It gives consumers a usable plan, create, check and update sequence and
           identifies the authoritative detailed interface contract. */
        attribute redefines rationale = "A reusable authoring facility is not usable across projects when consumers cannot discover its supported operations and their constraints from the distributed kit.";
    }

    requirement structuredDocumentationEvidenceIsReviewable : XDesignRequirement {
        @XDesignCommon::DocSection { document = "docs/requirements/requirements.md"; section = "R20"; }
        doc /* Proposed; no design satisfier yet. Verification retains assessed
           source revision, selected and effective contract versions and digests,
           caller inputs, generated paths and hashes, commands, outcomes, diagnostics,
           unchanged-byte evidence for failures, compiler limitations and permitted
           reviewer judgment. Deterministic structural findings are reported separately
           from semantic assessment of API and flow content, model alignment and
           visual fidelity; a structural pass is not engineering acceptance. */
        attribute redefines rationale = "A reviewer needs to reproduce the exact authoring and compatibility evidence and distinguish mechanical conformance from the truth and usefulness of the engineering design.";
    }


    requirement linkedWorktreeStoreIsIsolated : XDesignRequirement {
        @XDesignCommon::DocSection { document = "docs/requirements/requirements.md"; section = "R21"; }
        doc /* With no explicit root, a project in a valid linked Git worktree uses a
           dedicated operational store beneath the effective user's ~/.xdesign, not the
           worktree's .xdesign. Primary checkouts and non-Git projects retain the
           project-local default. A canonical project root and validated repository and
           worktree identity determine a stable binding: aliases of one project agree,
           while distinct projects, repositories and linked worktrees do not share a
           default store, even with equal names or wish IDs. An unresolvable home,
           ambiguous worktree identity or unverified binding fails explicitly without
           falling back to a local or another project's store. */
        attribute redefines rationale = "Worktree-local operational directories are easy to confuse or conflict with project content, while an unscoped global store would mix independent histories.";
    }

    requirement storeRootSelectionIsConsistent : XDesignRequirement {
        @XDesignCommon::DocSection { document = "docs/requirements/requirements.md"; section = "R21"; }
        doc /* For storage CLI commands, an explicit --root takes precedence over
           XDESIGN_STORE_ROOT and the default; for Web, --store-root takes precedence
           over that environment variable and the default. The lifecycle CLI uses the
           environment variable before the default; the storage API continues to use
           its supplied root. Relative CLI roots resolve against the invocation's project
           directory and Web roots against its selected project root. An empty explicit
           root is refused. Explicit selection does not trigger migration or adoption of
           another root and remains subject
           to integrity and migration fences. Web reads, health and delegated lifecycle
           operations use the same effective root, including an explicit Web override. */
        attribute redefines rationale = "A caller's explicit location must keep its established meaning, and readers and writers for one operator session must never act on different stores.";
    }

    requirement globalStoreNamespaceProtectsOtherContent : XDesignRequirement {
        @XDesignCommon::DocSection { document = "docs/requirements/requirements.md"; section = "R21"; }
        doc /* The global ~/.xdesign directory is a container, not itself a store root.
           A worktree uses its own dedicated child location, with an inspectable binding
           to its project and worktree identity. Existing unrelated content in the home
           directory remains untouched. If ~/.xdesign is itself an existing store root,
           refuse to place a child there and diagnose the conflict. A foreign, unsafe,
           incompatible, unreadable or mismatched destination and any detected binding
           collision refuse adoption and creation without changing that content. The
           selected location is reported. */
        attribute redefines rationale = "Existing tools or projects may already own content under the home directory, and equal names or a hash collision must not turn foreign data into this project's authority.";
    }

    requirement worktreeStoreMigrationPreservesHistory : XDesignRequirement {
        @XDesignCommon::DocSection { document = "docs/requirements/requirements.md"; section = "R21"; }
        doc /* Provide an explicit supported migration from a valid, quiescent linked
           worktree's old project-local store to its isolated global default. Before
           cutover, verify the complete logical source and destination: all generic items,
           kinds, heads, immutable revisions, metadata and complete URI/role/digest/length
           manifests; all referenced exact material bytes; and exact operation requests,
           terminal outcomes and results. Preserve those facts without inventing revisions,
           assessments or receipts. Preserve the store identity or retain an inspectable
           source-to-destination identity mapping. Rebind destination filesystem identity
           only through the verified migration; never treat a raw copy or move as a valid
           restored store. Unsupported, corrupt or unresolved pending state is refused. */
        attribute redefines rationale = "Location compatibility requires the old history and its evidence to remain examinable, while the existing store's recorded filesystem identity makes a raw copy unsafe.";
    }

    requirement migratedRunsKeepTheirLifecycle : XDesignRequirement {
        @XDesignCommon::DocSection { document = "docs/requirements/requirements.md"; section = "R21"; }
        doc /* After verified migration, store-backed SimpleFlow and WishVerifyFlow runs
           retain wish and run identity, frozen plan and work, visits, revisions, gate
           assessments, evidence, derived status, operation receipts and state tokens for
           unchanged heads. An active or blocked run can continue under the existing stale
           result and expected-head guards; a completed run stays completed and next/check
           do not add a revision or reopen it. Exact terminal operation retries return the
           retained outcome without a duplicate effect. Cache loss remains recoverable from
           migrated material, while changed workspace artifacts are not overwritten. */
        attribute redefines rationale = "A migration that merely finds the latest wish name but breaks continuation, completed history, or exact retries is not compatible with an existing run.";
    }

    requirement worktreeStoreConflictsFailClosed : XDesignRequirement {
        @XDesignCommon::DocSection { document = "docs/requirements/requirements.md"; section = "R21"; }
        doc /* When an old local store or an unclassifiable local candidate exists,
           default operations must not silently create or use an unrelated empty global
           store; diagnose it and require explicit migration or selection.
           If local and global stores both exist, use the global store by default only
           when durable migration provenance verifies their relationship and the retained
           source has not changed since cutover. Otherwise diagnose the ambiguity before
           mutation. A source absent after verified cutover need not remain present.
           Never infer equivalence from
           names, paths, IDs, or matching heads alone; never merge or overwrite divergent
           histories automatically. Provide a safe way to inspect each selected root. */
        attribute redefines rationale = "A location switch, apparent duplicate, or later write to an old store can hide or fork operational history unless ambiguity is visible and writes stop.";
    }

    requirement worktreeMigrationHasRecoverableCutover : XDesignRequirement {
        @XDesignCommon::DocSection { document = "docs/requirements/requirements.md"; section = "R21"; }
        doc /* Migration requires the operator to stop non-cooperating older clients and
           reconcile pending operations and writer locks before it begins. Supported new
           readers and writers coordinate with migration so no source or destination write
           races verification or cutover. The source remains recoverable and is not deleted
           or overwritten by migration. A durable decision distinguishes incomplete work
           from verified cutover; before that decision the destination is not authoritative,
           and afterward the verified destination is authoritative. Supported clients
           refuse writes to the retained source while that cutover stands. On interruption
           or an uncertain response, inspection and exact retry recover one outcome; before
           the decision a safe rollback may instead leave the source authoritative. Default
           operations do not create a fresh store or use unverified partial state.
           Diagnostics identify roots, status and safe next action. */
        attribute redefines rationale = "Copying while another process writes or losing a process at cutover can otherwise produce two divergent authorities or destroy the only usable history.";
    }

    requirement legacyCacheRegistrationsStayLegacy : XDesignRequirement {
        @XDesignCommon::DocSection { document = "docs/requirements/requirements.md"; section = "R21"; }
        doc /* Existing legacy cache-backed registrations and Git wish traces keep their
           existing backend and history; location migration neither imports, discards nor
           treats their cache as disposable store-backed material. Legacy active and
           completed runs remain readable and retain their existing lifecycle behavior.
           Classify a genuine legacy registry separately from a regenerable store-backed
           cache. If a genuine legacy registration and a selected persistent item have
           the same wish ID, diagnose the ambiguity, permit read-only inspection of
           both and refuse mutation rather than silently selecting, overwriting or
           merging either history. */
        attribute redefines rationale = "Legacy cache registrations are authoritative for their own runs, unlike a store-backed working cache, and a matching local wish ID is not proof of one history.";
    }

    requirement documentKitCatalogHasCoherentResourceLayout : XDesignRequirement {
        @XDesignCommon::DocSection { document = "docs/requirements/requirements.md"; section = "R22"; }
        doc /* Proposed; no design satisfier yet. The new bundled catalog organizes its
           21 entries into entry-owned packages with language-scoped template, guide,
           complete fictional example and full-input fixture resources. Shared
           language-neutral resources have separate shared homes. The manifest binds
           every resource role and language to exactly one normalized, digest-covered
           authoritative path. Discovery uses those explicit declarations, not directory
           globs, network lookup or editable mirror trees. The bundled layout has 21
           entry directories, 42 language variants and 168 language-specific resources;
           missing, duplicate, ambiguous or competing declarations fail before writes. */
        attribute redefines rationale = "One inspectable owner for every logical resource variant prevents divergent translations and duplicate editing while making the complete catalog discoverable without knowing incidental filenames.";
    }

    requirement documentKitSupportsCompleteChineseAndEnglish : XDesignRequirement {
        @XDesignCommon::DocSection { document = "docs/requirements/requirements.md"; section = "R22"; }
        doc /* Proposed; no design satisfier yet. Every one of the 21 existing entries
           has complete en and zh-CN variants, not a translated sample subset. Each
           variant supplies its template, guide, complete fictional example and
           full-input fixture. Both languages preserve class, template ID, route,
           ordered section and required-field semantics, checks, view concerns,
           anchor/model rules and equivalent engineering obligations; headings,
           guidance, examples and fixture prose may be localized. Fixtures identify
           their language and a same-language expected document. All 42 variants
           support complete plan/create/check authoring, with no unresolved
           placeholder, missing translation or silent English substitution. */
        attribute redefines rationale = "Bilingual authoring is usable only when every engineering entry and its supporting inputs are available in both languages with equivalent structure and meaning.";
    }

    requirement documentTemplateLanguageSelectionIsDeterministic : XDesignRequirement {
        @XDesignCommon::DocSection { document = "docs/requirements/requirements.md"; section = "R22"; }
        doc /* Proposed; no design satisfier yet. The bundled language IDs are exactly
           case-sensitive en and zh-CN, and the declared default is en. Plan/create
           and language-addressed resource reads accept an explicit selector; omission
           under the new release selects en. Locale, environment and document content
           are never inferred as language, and an unsupported variant never falls back
           to English. A well-formed unsupported ID reports unknown-language; malformed
           or conflicting selectors report invalid-request before writes. Language does
           not change the class/name/layer route or permit a same-path overwrite.
           Original packs have no language axis: a supplied selector is invalid-request,
           while omission retains their original behavior. */
        attribute redefines rationale = "Explicit, deterministic selection lets a caller predict the authoring language and failure behavior without hidden locale dependence or destructive fallback.";
    }

    requirement documentTemplateLanguageIdentityIsPersistent : XDesignRequirement {
        @XDesignCommon::DocSection { document = "docs/requirements/requirements.md"; section = "R22"; }
        doc /* Proposed; no design satisfier yet. New-release creation records the
           selected language consistently in the document marker, registry and
           effective identity, and responses and checks expose it. Update, attachment
           and checking resolve the recorded variant rather than a changed default or
           caller preference. A same-path creation in another language remains a
           collision, not a conversion. Missing, unsupported or disagreeing persisted
           language identity fails registry-mismatch without adoption or migration;
           original language-less identities are never backfilled. New stored examples
           retain the one-contract-sentinel convention, and acceptance comparison also
           asserts their actual language while replacing only the contract field. */
        attribute redefines rationale = "Persisted language identity keeps later edits and validation attached to the contract actually authored instead of silently reinterpreting a document after defaults change.";
    }

    requirement documentTemplateLanguageSurfacesAreShared : XDesignRequirement {
        @XDesignCommon::DocSection { document = "docs/requirements/requirements.md"; section = "R22"; }
        doc /* Proposed; no design satisfier yet. Python, the JSON CLI and bound stdio
           MCP expose equivalent language selection, defaults, effective identities,
           validation and discovery for all 21 entries. Their contract/catalog surface
           enumerates every language variant and the locations and exact bytes of its
           template, guide, example and fixture; language-addressed reads return the
           selected bytes, and examples never become template selections. New Python
           selection is additive and keyword-only, CLI uses a documented option and MCP
           uses equivalent arguments/resources, retaining existing operation names,
           positional parameters and MCP root/profile binding. Equivalent requests
           produce equivalent routes, bytes, identities and diagnostics within their
           transport envelopes. */
        attribute redefines rationale = "Authors need the same complete bilingual resources and decisions regardless of transport, without adapter-specific fallback or resource discovery forks.";
    }

    requirement chineseTemplatesUseScholarlyEngineeringProse : XDesignRequirement {
        @XDesignCommon::DocSection { document = "docs/requirements/requirements.md"; section = "R22"; }
        doc /* Proposed; no design satisfier yet. Chinese template guidance, guides,
           examples and fixture prose use precise consistent terminology, an objective
           tone, complete coherent paragraphs and traceable reasoning. Each engineering
           class develops problem or context, rationale, method or design, evidence or
           verification, and limitations to the extent appropriate to that class; no
           thesis-only chapter set replaces those classes. No citation, source,
           standard, model fact, implementation, test or review result is fabricated.
           English variants retain equivalent normative meaning rather than requiring
           literal word-for-word translation. A permitted reviewer independent of the
           author reviews every one of the 21 language pairs section by section. */
        attribute redefines rationale = "Scholarly engineering prose improves precision and auditability only when applied to the whole engineering catalog with verifiable claims, not when reduced to academic formatting or selected examples.";
    }

    requirement bilingualDocumentKitPreservesCompatibility : XDesignRequirement {
        @XDesignCommon::DocSection { document = "docs/requirements/requirements.md"; section = "R22"; }
        doc /* Proposed; no design satisfier yet. The bilingual catalog has a new
           version and digest and retains the exact current 1.0.0, 1.1.0 and 1.2.0
           resource closures as independently selectable compatibility packs, including
           nested closures and original behavior. Existing positional calls, document
           routes and language-less effective identities remain valid under their
           original packs. The new release resolves supported old and new pages under
           each page's effective contract without implicit migration, adoption,
           language backfill or edits to unmanaged and historical artifacts. Retained
           immutable compatibility bytes are not duplicate editable current sources.
           Original packs may refuse foreign new identities as before. */
        attribute redefines rationale = "Reorganizing and translating the current catalog must not redefine released contracts, strand consumers or rewrite the basis of existing documents and evidence.";
    }

    requirement bilingualDocumentKitEvidenceIsReviewable : XDesignRequirement {
        @XDesignCommon::DocSection { document = "docs/requirements/requirements.md"; section = "R22"; }
        doc /* Proposed; no design satisfier yet. Verification binds the assessed source
           revision, old and new contract identities and digests, the complete resource
           coverage matrix, exact caller inputs and outputs, resource and document
           hashes, commands, exits, transcripts, failure-preservation evidence,
           diagnostics, skips and unevaluated checks. It separately retains reviewer
           identity and authority, per-entry Chinese quality and English-equivalence
           judgments, findings and residual risks. A missing variant, case or required
           semantic review prevents bilingual acceptance; compiler, structural and
           requirements-stage checks are not product acceptance. */
        attribute redefines rationale = "Complete, revision-bound evidence distinguishes genuine bilingual coverage and scholarly quality from a few successful translations or mechanical checks.";
    }
}
